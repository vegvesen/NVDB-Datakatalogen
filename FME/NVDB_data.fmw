FME workspace NVDB_data.fmw

Parameters:
- AndreParametre =
- DestDataset_GEODATABASE_FILE =
- GeomatrifilterJsonURL =
- GeometrifilterWKT =
- Geometrifilterbbox =
- Objekttyper =
- Vegkategori =
- Vegstatus =
- type_strukt =
- utFormat =
- utKoordSys =

Writers:
- GEODATABASE_FILE_1: GEODATABASE_FILE to $(DestDataset_GEODATABASE_FILE)

Note: Om workspacet / Henter objekttyper fra NVDB les-API / Versjon av API: https://nvdbapiles-v3.atlas.vegvesen.no/ / Input: / Se boks Input-parametre / Output: / To utformater (GML og GDB) er implementert. / Brukere kan implementere nye utformater og/eller utvide med egen forretningslogikk. Dema eksport til ledningsregistreringsforskriften er eksempel. / Utviklet av Knut Jetlund og Ingar Skogli / Statens vegvesen september 2021
Creator
    GEOMTYPE = Geometry Object
    NUM = 1
    CREATED -> NVDBAPIlesFilterGeometriInn
Note: Input-parametre / Dokumentasjon NVDB les-API: / https://nvdbapiles-v3.atlas.vegvesen.no/dokumentasjon/openapi/#/Vegobjekter/get_vegobjekter__vegobjekttypeid_ / Parametre - eksempler/dokumentasjon/info: / Objekttper: / Leveranse prosjekt: 532;98;79;95 / Ledningsregistreringsforskriften: 77;79;83;92;852;853;939;843;882;80;208;209;82;78;844;876;85;210;828 / Elveg2.0: 923;924;105;721;821;538;813;591;606;100;822;595;573;856;607;107;532 / Andre filtre: / Eksempel: / kommune=3001,3002&overlapp=67 / Hamar = 3403 / Geometri / Geometri json URL: / Definer i Norgeskart.no (epsg-kode 4326) / Eksempel: https://www.norgeskart.no/ws/get-json.py?hash=Oc6JcHkB1BVmjWzlBFjs&save=true / Geometri WKT: / UTM sone 33 / Eksempel Hamar sentrum: / POLYGON((286793.02 6746649.26,287158.62 6746653.89,287150.7 6746448.6,286834.71 6746409.62,286793.02 6746649.26)) / For andre formater og koordinatsystemer, legg til transformere som kobler til denne. / Geometrifilter bbox: / Dokumentasjon: https://api.vegdata.no/parameter/lokasjonsfilter.html / UTM sone 33 / Eksempel Hamar sentrum: / &kartutsnitt=286793,6746448,287150,6746649
NVDBAPIlesFilterGeometriInn
    GeometrifilterJsonURL = $(GeomatrifilterJsonURL)
    GeometrifilterWKT = $(GeometrifilterWKT)
    Geometrifilterbbox = $(Geometrifilterbbox)
    -> NVDBAPIlesFilter
NVDBAPIlesFilter
    AndreParametre = $(AndreParametre)
    Objekttyper = $(Objekttyper)
    Polygon = @Value(Polygon)
    Vegkategori = $(Vegkategori)
    Vegstatus = $(Vegstatus)
    kartutsnitt = @Value(kartutsnitt)
    Output_href -> NVDBAPIlesVegobjekter [Input_href]
NVDBAPIlesVegobjekter
    NESTE.HREF = @Value(href)
    _FTID = @Value(_ftID)
    gmlFolder = $(mainFolder)\GML
    kommune = 1857
    mainFolder = C:\DATA\GIT\SOSI-Vegnett
    type_strukt = $(type_strukt)
    Output_feature -> Transformer [Tester_Input]
Transformer
    utKoordSys = EPSG:25833
    AttributeRemover_Output -> TestFilter
Note: Oppslag mot NVDB skjer i UTM sone 33 fordi: / 1. APIet har ikke konsekvent angivelse av srid: utm32, 4623 / 2. APIet har ulik håndtering av rekkefølge på nord- og øst-korrdinat: / json Øst, Nord / wkt Øst, Nord / NVDB kall pol utm Øst, Nord / NVDB kall pol 4326 Nord, Øst / NVDB resultat Som kall / 3. FME støtter ikke koordsys som inkluderer norske høydreref?
TestFilter
    DEFAULT_VALUE = <UNFILTERED>
    TEST_LIST = "BOOL_OP,OR,COMPOSITE_TEST,""""""1"""""",TEST_CLAUSE,TEST $(utFormat) = GML",ut-format = GML,"BOOL_OP,OR,COMPOSITE_TEST,""""""1"""""",TEST_CLAUSE,TEST $(utFormat) = GDB",ut-format = GDB
    ut-format = GML -> SchemaSetter_2 [Input_2]
    ut-format = GDB -> SchemaSetter [Input_2]
    <UNFILTERED> -> _

Bookmark: Skriv GML
SchemaSetter_2
    ForceDataType = No
    SORT = None
    Output_2 -> AttributeCreator
AttributeCreator
    ATTR_TABLE = SET_TO xsd = https://raw.githubusercontent.com/vegvesen/NVDB-Datakatalogen/master/GML//@Value(_ftID).xsd
    -> FeatureWriter [Output]
FeatureWriter
    DATASET = C:\_temp\@Value(fme_feature_type).gml
    DATASET_ATTR = _dataset
    FEATURE_TYPE_LIST_ATTR = _feature_type
    FORMAT = GML
    GML_COORDINATE_SYSTEM_GRANULARITY = DATASET
    GML_DESTINATION_DATASETTYPE_VALIDATION = Yes
    GML_GUESS_GEOMETRY_NAMES = YES
    GML_INDENT_SIZE = 1
    GML_MAP_ALL_SUBSTITUTABLE_PROPERTIES = YES
    GML_MAP_COMPLEX_PROPERTIES_AS = Nested Attributes
    GML_MAP_EMBEDDED_OBJECTS_AS = ATTRIBUTES
    GML_MAP_PREDEFINED_GML_PROPERTIES = NO
    GML_OUTPUT_ENCODING = utf-8
    GML_PREFER_POLYGON_OVER_SURFACE = no
    GML_PRETTY_PRINT = No
    GML_PROFILE = GML Application Schema
    GML_REPLACE_TABS_WITH_SPACES = No
    GML_SUPPRESS_XSI_SCHEMALOCATION = no
    GML_TEXT_INDENT = No
    GML_USE_STYLESHEET_RESULT_AS_DATASET = no
    GML_VALIDATE_OUTPUT_DATASET = NO
    GML_XSD_DOC = @Value(xsd)
    TOTAL_FEATURES_WRITTEN_ATTR = _total_features_written

Bookmark: Skriv GDB
SchemaSetter
    ForceDataType = No
    SORT = None
    Output_2 -> GeometryFilter
GeometryFilter
    BREAK_AGG = No
    GEOM_PORT_NAMES = Point Line Arc Area
    POINT -> FeatureClass1 (writer GEODATABASE_FILE_1)
    LINE -> FeatureClass100 (writer GEODATABASE_FILE_1)
    ARC -> FeatureClass10000 (writer GEODATABASE_FILE_1)
    AREA -> FeatureClass10000 (writer GEODATABASE_FILE_1)
FeatureClass1 (writer GEODATABASE_FILE_1)
FeatureClass100 (writer GEODATABASE_FILE_1)
FeatureClass10000 (writer GEODATABASE_FILE_1)

Bookmark: FME Inspector
_: Inspector
    TACKATTRS = fme_feature_type

FME custom transformer SchemaSetter
This transformer adds both exposed and unexposed attributes to a feature-based schema, with appropriate data types. 
For example: if a feature has the following attributes:
Attribute(boolean) : 'mybool' has value 'Yes' 
Attribute(32 bit integer): 'myint' has value '12' 
Attribute(64 bit real) : 'myreal' has value '12.965' 
the following list attributes will be added:
Attribute(string) : 'attribute{0}.fme_data_type' has value 'fme_boolean' 
Attribute(encoded: utf-8): 'attribute{0}.name' has value 'mybool' 
Attribute(string) : 'attribute{1}.fme_data_type' has value 'fme_int32' 
Attribute(encoded: utf-8): 'attribute{1}.name' has value 'myint' 
Attribute(string) : 'attribute{2}.fme_data_type' has value 'fme_real64' 
Attribute(encoded: utf-8): 'attribute{2}.name' has value 'myreal' 
The transformer also gives users the option to exclude certain attributes based on name or prefix, and automatically excludes all "fme_" attributes.  Another option exists to force all attributes to string data type in the case of mismatches in the source attributes.
Input Ports 
Features containing attributes for which a schema definition is required. 
Output Ports 
All features are output. Attributes which have been selected to be excluded are removed from the feature. The list containing the schema of the feature is added to each feature. 
Parameters 
Attributes to Exclude 
A selected set of attributes that will be excluded from the generated schema list and removed from the feature.
Prefixes to Exclude 
A comma-delimited list of prefixes for attributes that are to be excluded from the generated schema list and removed from the feature. Regular expressions are not supported. For example: "date" will exclude any attributes that start with the letters "date" e.g. date_created, dateupdated
Sort Attributes 
(Ascending, Descending, None) Set this parameter to alphabetically sort output attributes.
Force attributes to strings:
If set to "No", the SchemaSetter will set the data type to the native attribute data type. If set to "Yes", the SchemaSetter will force all attribute data type sto "fme_char(255)".
Usage Notes 
The feature based schema can be passed to any writer that it set to Dynamic Mode and used with the "Schema from First Feature" setting.
Please see https://knowledge.safe.com/articles/1051/dynamic-workflow-tutorial-destination-schema-is-de-2.html for more information on feature-based schema using list attributes.

Parameters:
- AttributesToExclude =
- ForceDataType =
- PrefixesToExclude =
- SORT =

Input_2 (input)
    -> ParameterFetcher
Note: Retrieve Parameters
ParameterFetcher
    ATTR_LIST = _AttributesToExclude $(AttributesToExclude) _PrefixesToExclude $(PrefixesToExclude) _sort $(SORT) _ForceDataType $(ForceDataType)
    -> PythonCaller
Note: See Comment in Code
PythonCaller
    PYTHONSOURCE:
      from __future__ import absolute_import, division, print_function, unicode_literals

      import fmeobjects
      import six

      #Checks if a list entry starts with a certain string
      def StringLikeList(list,string):
              test=False
              for element in list:
                  if string.startswith(element):
                      test=True
              return test

       # Checks if a list contains an element equal to a certain string
      def StringInList(list,string):
              test=False
              for element in list:
                  if string==element:
                      test=True
              return test

      # Template Class Interface:
      class FeatureProcessor(object):

          typesMapping = {
              fmeobjects.FME_ATTR_UNDEFINED : None,
              fmeobjects.FME_ATTR_BOOLEAN : "fme_boolean",
              fmeobjects.FME_ATTR_INT8 : "fme_int8",
              fmeobjects.FME_ATTR_UINT8 : "fme_uint8",
              fmeobjects.FME_ATTR_INT16 : "fme_int16",
              fmeobjects.FME_ATTR_UINT16 : "fme_uint16",
              fmeobjects.FME_ATTR_INT32 : "fme_int32",
              fmeobjects.FME_ATTR_UINT32 : "fme_uint32",
              fmeobjects.FME_ATTR_REAL32 : "fme_real32",
              fmeobjects.FME_ATTR_REAL64 : "fme_real64",
              fmeobjects.FME_ATTR_REAL80 : "fme_real80",
              fmeobjects.FME_ATTR_STRING : "fme_char(255)",
              fmeobjects.FME_ATTR_ENCODED_STRING : "fme_varchar(255)",
              fmeobjects.FME_ATTR_INT64 : "fme_int64",
              fmeobjects.FME_ATTR_UINT64 : "fme_uint64"
           }

          def __init__(self):
              pass
          def input(self,feature):
              #create a new feature
              nfeature=fmeobjects.FMEFeature()
              #get list of all attributes on feature
              attlist=feature.getAllAttributeNames()
              #loop through all attributes and add to schema if they fail exclusion criteria
              i=0
              ExcludedAttributes=str(feature.getAttribute('_AttributesToExclude')).split(",")
              ExcludedAttributes.append('_ForceDataType')
              ExcludedPrefixes=str(feature.getAttribute('_PrefixesToExclude')).split(",")

              # remove all fme_ attributes from list - don't want to include these in dynamic schema
              ExcludedPrefixes = ['fme_'] if ExcludedPrefixes == [''] else ExcludedPrefixes + ["fme_"]

              # sorting attributes
              if feature.getAttribute('_sort') == 'Ascending' or feature.getAttribute('_sort') == 'Descending':
                  attlist.sort()
                  if feature.getAttribute('_sort') == 'Descending':
                      attlist.reverse()

              for att in attlist:
                  if not StringInList(ExcludedAttributes,att) and not StringLikeList(ExcludedPrefixes,att) and not att=='_AttributesToExclude' and not att=='_PrefixesToExclude' and not att=='_sort':

                     #Check datatype and set in schema
                     if feature.getAttribute('_ForceDataType') == 'No':
                         type = feature.getAttributeType(att)
                         type = self.typesMapping[type]
                     #Force to string if user wishes
                     else:
                         type = "fme_char(255)"

                     if type is None:
                         feature.removeAttribute(att)
                     else:
                         #add schema attributes to feature
                         nfeature.setAttribute("attribute{"+str(i)+"}.fme_data_type",type)
                         nfeature.setAttribute("attribute{"+str(i)+"}.name",six.text_type(att))
                         nfeature.setAttribute(att,feature.getAttribute(att))
                         i+=1;
              #copy original geometry to new feature
              nfeature.setGeometry(feature.getGeometry())
              nfeature.setCoordSys(feature.getCoordSys())
              nfeature.setFeatureType(feature.getFeatureType())
              nfeature.setAttribute("fme_geometry{0}",feature.getAttribute("fme_type"))
              nfeature.setAttribute("fme_feature_type",feature.getAttribute("fme_feature_type"))
              print(i)
              self.pyoutput(nfeature)
          def close(self):
              pass
    PYTHONSYMBOL = FeatureProcessor
    -> Output_2 (output)
Output_2 (output)

FME custom transformer NVDBAPIlesFilter

Parameters:
- AndreParametre =
- Objekttyper =
- Polygon =
- Vegkategori =
- Vegstatus =
- kartutsnitt =

Input (input)
    -> AttributeCreator_2
AttributeCreator_2
    ATTR_TABLE:
      SET_TO vegkategori = $(Vegkategori)
      SET_TO vegstatus = $(Vegstatus)
      SET_TO vegsystemreferanse
      SET_TO AndreParametre = FME_CONDITIONAL:DEFAULT_VALUE'_FME_NO_OP_'BOOL_OP;OR;COMPOSITE_TEST;1;TEST $(AndreParametre) != _FME_BLANK_STRING_'&$(AndreParametre)'FME_NUM_CONDITIONS2___
    -> PythonCaller
Junction_2
    -> Tester_2
Junction_3
    -> AttributeManager_8
AttributeCreator
    ATTR_TABLE = SET_TO href = https://nvdbapiles-v3.atlas.vegvesen.no/vegobjekter/@Value(_ftID)?inkluder=egenskaper,geometri,metadata@Value(kartutsnitt)@Value(vegsystemreferanse)@Value(AndreParametre)@Value(polygon)&srid=utm33
    -> AttributeRemover_2
AttributeRemover_2
    REMOVE_ATTRS = _element_index,_xmax,_xmin,_ymax,_ymin,_zmax,_zmin,AndreParametre,ftIDs,kartutsnitt,vegkategori,vegstatus,vegsystemreferanse
    -> Output_href (output)
Output_href (output)

Bookmark: Sett filter Vegsystemreferanse
PythonCaller
    PYTHONSOURCE:
      import fme
      import fmeobjects

      def processFeature(feature):
          vk=feature.getAttribute('vegkategori')
          vs=feature.getAttribute('vegstatus')
          if vk=='' and vs=='':
              feature.setAttribute('vegsystemreferanse','')
          else:
              if vs=='':
                  feature.setAttribute('vegsystemreferanse','&vegsystemreferanse='+vk.replace(' ', ','))
              else:
                  vsLi=list(vs.split(" "))
                  if vk=='':
                      vk="E R F K P S"
                  vkLi=list(vk.split(" "))
                  xy=""
                  for x in vkLi:
                      for y in vsLi:
                          xy=xy+','+x+y
                  vref='&vegsystemreferanse='+xy[1:]
                  #print('vegsystemreferanse: '+vref)
                  feature.setAttribute('vegsystemreferanse',vref)

          pass
    PYTHONSYMBOL = processFeature
    -> Tester

Bookmark: Sett filter kartutsnitt
Tester
    BOOL_OP = OR
    COMPOSITE_TEST = 1
    TEST_CLAUSE = TEST $(kartutsnitt) = ""
    TEST_MODE = TEST
    PASSED -> AttributeCreator_3
    FAILED -> AttributeCreator_4
AttributeCreator_3
    ATTR_TABLE = SET_TO kartutsnitt
    -> Junction_2
AttributeCreator_4
    ATTR_TABLE = SET_TO kartutsnitt = $(kartutsnitt)
    -> Junction_2

Bookmark: Sett filter kartutsnitt
Tester_2
    BOOL_OP = OR
    COMPOSITE_TEST = 1
    TEST_CLAUSE = TEST $(Polygon) = ""
    TEST_MODE = TEST
    PASSED -> AttributeCreator_5
    FAILED -> AttributeCreator_6
AttributeCreator_5
    ATTR_TABLE = SET_TO polygon
    -> Junction_3
AttributeCreator_6
    ATTR_TABLE = SET_TO polygon = $(Polygon)
    -> Junction_3

Bookmark: Objekttyper
AttributeManager_8
    ATTR_TABLE = SET_TO ftIDs = $(Objekttyper)
    -> AttributeSplitter
AttributeSplitter
    ATTR_NAME = ftIDs
    DELIMITER = ;
    DROP_EMPTY_PARTS = No
    LIST_NAME = _ftID
    TRIM_OPTION = Both
    -> ListExploder_2
ListExploder_2
    ATTR_ACCUM_MODE = Merge List Attributes
    ATTR_CONFLICT_RES = Use List Attribute Values
    INDEX_ATTR = _element_index
    LIST_ATTR = _ftID{}
    ELEMENTS -> Junction
Junction
    -> AttributeCreator
AttributeManager_2 [off]
    ATTR_TABLE = SET_TO ftIDs = 821;105;813;591;606;100;822;573;856;607;107;923;924;721;595

FME custom transformer Transformer

Parameters:
- utKoordSys =

Tester_Input (input)
    -> Tester
Tester
    BOOL_OP = OR
    COMPOSITE_TEST = 1
    TEST_CLAUSE = TEST $(utKoordSys) = EPSG:25833
    TEST_MODE = TEST
    PASSED -> AttributeRemover
    FAILED -> Reprojector
Reprojector
    DEST = $(utKoordSys)
    INTERPOLATION_TYPE_NAME = Nearest Neighbor
    RASTER_CELL_SIZE = Preserve Cells
    RASTER_TOLERANCE = 0.0
    SOURCE = EPSG:25833
    REPROJECTED -> CoordinateSystemSetter_2
CoordinateSystemSetter_2
    COORDSYS = $(utKoordSys)
    -> AttributeRemover
AttributeRemover
    REMOVE_ATTRS = _clipped,_creation_instance,_part_number,gml_id,href,kommunenummer,geometri.wkt
    -> AttributeRemover_Output (output)
AttributeRemover_Output (output)

FME custom transformer NVDBAPIlesFilterGeometriInn

Parameters:
- GeometrifilterJsonURL =
- GeometrifilterWKT =
- Geometrifilterbbox =

Input (input)
    -> Tester
Note: GeometrifilterJsonURL
Tester
    BOOL_OP = OR
    COMPOSITE_TEST = 1
    TEST_CLAUSE = TEST $(GeometrifilterJsonURL) != ""
    TEST_MODE = TEST
    PASSED -> FeatureReader [INITIATOR]
    FAILED -> Tester_2
Note: GeometrifilterWKT
Tester_2
    BOOL_OP = OR
    COMPOSITE_TEST = 1
    TEST_CLAUSE = TEST $(GeometrifilterWKT) != ""
    TEST_MODE = TEST
    PASSED -> GeometryReplacer
    FAILED -> Tester_3
GeometryReplacer
    KIND_LONG = OGC Well Known Text
    OGC_WKT_PRECISION_DISPLAY = 64-bit
    REMOVE_ATTRIBUTE = Yes
    SOURCE = $(GeometrifilterWKT)
    -> Junction_2
CoordinateExtractor_Output: Logger
    LOG_FEATURE = LOG_ONLY
    MAXCOORDS = 20
    MAXFEATS = 20
    MESSAGE = Feature is:
    SEVERITY = INFO
Note: Geometrifilterbbox
Tester_3
    BOOL_OP = OR
    COMPOSITE_TEST = 1
    TEST_CLAUSE = TEST $(Geometrifilterbbox) != ""
    TEST_MODE = TEST
    PASSED -> AttributeCreator_2
    FAILED -> Junction
AttributeCreator_2
    ATTR_TABLE = SET_TO kartutsnitt = $(Geometrifilterbbox)
    -> Junction
Junction
    -> Output (output)
Note: KlippegeometriWKT fra gitt kilde
Output (output)

Bookmark: Feometri - Json URL
FeatureReader
    ATTR_ACCUM_MODE = Only Use Result
    COMBINE_GEOM = Use Result
    DATASET = $(GeometrifilterJsonURL)
    FORMAT = GEOJSON
    GEOJSON_FLATTEN_MODE = ALL_LEVELS
    GEOJSON_USE_BASENAME_AS_DEFAULT_FEATURE_TYPE = Yes
    GEOJSON_USE_SEARCH_ENVELOPE = NO
    INTERACT = <No Spatial Filter>
    OUTPUT_FEATURES_DISPLAY = Schema and Data Features
    <OTHER> -> Reprojector
Reprojector
    DEST = EPSG:25833
    INTERPOLATION_TYPE_NAME = Nearest Neighbor
    RASTER_CELL_SIZE = Preserve Cells
    RASTER_TOLERANCE = 0.0
    SOURCE = EPSG:4326
    REPROJECTED -> Junction_2

Bookmark: Utsnitt og klippegeometri
Junction_2
    -> AttributeRemover
AttributeRemover
    REMOVE_ATTRS = _xmax,_xmin,_ymax,_ymin,_zmax,_zmin
    -> GeometryExtractor
GeometryExtractor
    ATTR = KlippegeometriWKT
    KIND_LONG = OGC Well Known Text
    OGCVERSION = 1.2
    OGC_WKT_PRECISION_DISPLAY = 64-bit
    PREFER_POLYGON_OVER_SURFACE = No
    REMOVE_GEOMETRY = No
    -> AttributeCreator
AttributeCreator
    ATTR_TABLE = SET_TO Polygon = &polygon=@Substring(@Value(KlippegeometriWKT),10,@StringLength(@Value(KlippegeometriWKT))-12)
    -> CoordinateExtractor_Output
    -> Junction

FME custom transformer NVDBAPIlesVegobjekter
Leser NVDB API les.
Input: href
Output: NVDB API features

Parameters:
- FME_USER_PARAM_PRIVATE_GRP =
- NESTE.HREF =
- _FTID =
- gmlFolder =
- kommune =
- mainFolder =
- type_strukt =

Note: Kan det defineres at et element SKAL blli en liste? Vil i så fall kunne forenkle koden i NVDBTranslator mye. / Se under cardinality under dokumentasjon i XML Fragmenter
Input_href (input)
    -> HTTPCaller_3
Loop (input)
    -> HTTPCaller_3
HTTPCaller_3
    CONNECTION_TIMEOUT_LENGTH = 60
    CUSTOM_HEADERS = Accept;application/vnd.vegvesen.nvdb-v3-rev1+xml
    ERROR_ATTR = _error
    FOLLOW_REDIRECTS = Yes
    HTTP_METHOD = GET
    RESPONSE_HEADER_LIST_ATTR = _headers
    SAVE_FILE = Attribute
    STATUS_CODE_ATTR = _http_status_code
    TARGET_ATTR = _url_contents
    TARGET_ATTR_ENCODING = auto-detect
    TARGET_URL = @Value(neste.href)
    TRANSFER_TIMEOUT_LENGTH = 90
    USE_COOKIES = No
    VERIFY_SSL_CERTIFICATES = Yes
    -> AttributeRemover_2
    -> PythonCaller_3
Note: Slå opp objekttype
PythonCaller_3
    NEW_ATTRIBUTES = XMLObjekttype
    PYTHONSOURCE:
      import fme
      import fmeobjects
      from urllib.request import Request, urlopen
      import xml.etree.ElementTree as ET
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              ft=str(feature.getAttribute('_ftID'))
              url = "https://nvdbapiles-v3.atlas.vegvesen.no/vegobjekttyper/" + str(ft) + "?inkluder=egenskapstyper"
              req = Request(url)
              req.add_header('Accept', 'application/xml')
              content = urlopen(req).read()
              feature.setAttribute('XMLObjekttype', content)
              self.pyoutput(feature)
          def close(self):
              pass
    PYTHONSYMBOL = FeatureProcessor
    -> XMLFragmenter
Note: Deler opp i en XML pr vegobjekt
XMLFragmenter
    ATTRIBUTE_XML = _url_contents
    EMBEDDED_EXPRESSIONS = vegobjekt
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = id geometri.wkt
    XML_SOURCE_TYPE = Attribute with XML document
    FRAGMENTS -> NVDBTranslator_2
Note: Oversetter fra NVDB-API-XML
NVDBTranslator_2: PythonCaller
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg kommunenummer startdato LinearLocationReference.networkReference{}.SimpleLinearReference.element.xlink_href LinearLocationReference.networkReference{}.SimplePointReference.element.xlink_href LinearLocationReference.networkReference{}.SimpleLinearReference.fromPosition.LR_DistanceExpression.distanceAlong LinearLocationReference.networkReference{}.SimpleLinearReference.toPosition.LR_DistanceExpression.distanceAlong LinearLocationReference.networkReference{}.SimplePointReference.atPosition.LR_DistanceExpression.distanceAlong LinearLocationReference.networkReference{}.SimpleLinearReference.fromPosition.LR_DistanceExpression.distanceAlong.uom LinearLocationReference.networkReference{}.SimpleLinearReference.toPosition.LR_DistanceExpression.distanceAlong.uom LinearLocationReference.networkReference{}.SimplePointReference.atPosition.LR_DistanceExpression.distanceAlong.uom LinearLocationReference.networkReference{}.SimpleLinearReference.applicableDirection LinearLocationReference.networkReference{}.SimplePointReference.applicableDirection
    PYTHONSOURCE:
      import fme
      import fmeobjects
      import xml.etree.ElementTree as ET

      def extractNVDB_XML(feature):

          ns='vegvesen.no.nvdb' # FME_MacroValues['namespace']
          #print('objektid: '+str(feature.getAttribute('id')))

           # Setter feature type
          if FME_MacroValues['type_strukt']=='sosinavn' or FME_MacroValues['utFormat']=='GML':

              tre = ET.fromstring(feature.getAttribute('XMLObjekttype'))
              e = tre.findall('sosinavn')
              for i in e:
                  ft = str(i.text)
          elif FME_MacroValues['type_strukt']=='navn':
              ft=str(feature.getAttribute('metadata.type.navn'))
          else:
              ft=str(feature.getAttribute('metadata.type.id'))


          #ft=str(feature.getAttribute('metadata.type.id'))


          feature.setAttribute('fme_feature_type',ft)
          feature.removeAttribute('metadata.type.id')
          # ID og versjon
          feature.setAttribute('identifikasjon.Identifikasjon.navnerom', ns)
          v=feature.getAttribute('id')
          feature.setAttribute('NVDB_ID', v)
          feature.setAttribute('identifikasjon.Identifikasjon.lokalId', v)
          feature.setAttribute('gml_id', ns + '.' + v)
          feature.removeAttribute('id')
          v=feature.getAttribute('metadata.versjon')
          feature.setAttribute('versjonsID', v)
          feature.setAttribute('identifikasjon.Identifikasjon.versjonId', v)
          feature.removeAttribute('metadata.versjon')

          #Geometri
          v=feature.getAttribute('geometri.wkt')
          if v != None:
              feature.setAttribute('geometri', v)
          feature.removeAttribute('geometri.wkt')
          v=feature.getAttribute('geometri.egengeometri')
          if v != None:
              feature.setAttribute('egengeometri', v)
          if v == 'true':
              feature.setAttribute('prosesshistorie', 'Geometri: Egengeometri fra NVDB')
          else:
              feature.setAttribute('prosesshistorie', 'Geometri: Generert fra lineære referanser til vegnett i NVDB')
          feature.removeAttribute('geometri.egengeometri')
          v=feature.getAttribute('geometri.srid')
          if v != None:
              feature.setAttribute('epsg', 'EPSG:'+v)
          feature.removeAttribute('geometri.srid')

          # Henter ut egenskaper
          i = 0
          sisteEgenskap=False
          while sisteEgenskap==False:

              if FME_MacroValues['type_strukt']=='sosinavn' or FME_MacroValues['utFormat']=='GML':
                  egenskapsid = feature.getAttribute('egenskaper.egenskap{%d}.id' % i)
                  tre = ET.fromstring(feature.getAttribute('XMLObjekttype'))
                  e = tre.findall('egenskapstyper/egenskapstype[id = "' + str(egenskapsid) + '"]/sosinavn')
                  funnet = False
                  for node in e:
                      n = node.text
                      funnet = True
                  if funnet == False:
                      n = egenskapsid
              elif FME_MacroValues['type_strukt']=='navn':
                  n = feature.getAttribute('egenskaper.egenskap{%d}.navn' % i)
              else:
                  n = feature.getAttribute('egenskaper.egenskap{%d}.id' % i)

              e = str(feature.getAttribute('egenskaper.egenskap{%d}.enum_id' % i))
              v = feature.getAttribute('egenskaper.egenskap{%d}.verdi' % i)
              #if v == None:
              #    if i==0:
              #        # 1. egenskap, ikke liste
              #        n = feature.getAttribute('egenskaper.egenskap.id')
              #        e = str(feature.getAttribute('egenskaper.egenskap.enum_id'))
              #        v = feature.getAttribute('egenskaper.egenskap.verdi')

              if n == None:
                  sisteEgenskap=True
              else:
                      if e == 'None' or FME_MacroValues['type_strukt']=='navn' or FME_MacroValues['type_strukt']=='sosinavn' or FME_MacroValues['utFormat']=='GML':
                          # if (n == 'Kommunenummer' and v == 0):
                          if v != None:
                              feature.setAttribute(n, v)
                              #print(str(n)+"="+str(v)+' (v), i:'+str(i))
                      else:
                          # Enumverdi for kodelisteverdier
                          feature.setAttribute(n, e)
                          #print(str(n)+"="+str(e)+' (e), i:'+str(i))
              i += 1
          #feature.removeAttribute('egenskaper.egenskap{}')
    PYTHONSYMBOL = extractNVDB_XML
    -> AttributeExposer_2
AttributeExposer_2
    ATTR_LIST = egenskaper.egenskap{}
    -> AttributeRemover
AttributeRemover
    LIST_ATTRS = egenskaper.egenskap{}
    -> GeometryReplacer
CoordinateSystemSetter_3
    COORDSYS = EPSG:25833
    -> Deaggregator
AttributeRemover_4
    LIST_ATTRS = _headers{} _headers{}.name _headers{}.value _hierarchy_child_id_list{}
    REMOVE_ATTRS = XMLObjekttype,_geometry_name,_headers{0}.name,_headers{0}.value,startdato,xml_fragment,xml_id,xml_matched_element,xml_parent_child_pos,xml_parent_id,_hierarchy_child_id_list{0},_hierarchy_id,_hierarchy_parent_id,_http_status_code,_url_contents,neste.href
    -> Output_feature (output)
Output_feature (output)
AttributeRemover_2
    LIST_ATTRS = _headers{}.name _headers{}.value
    REMOVE_ATTRS = _http_status_code,returnert,xml_fragment,xml_id,xml_matched_element,xml_parent_child_pos,xml_parent_id
    -> XMLFragmenter_2
XMLFragmenter_2
    ATTRIBUTE_XML = _url_contents
    EMBEDDED_EXPRESSIONS = side/metadata
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = returnert neste.href _ftID
    XML_SOURCE_TYPE = Attribute with XML document
    FRAGMENTS -> TestFilter
TestFilter
    DEFAULT_VALUE = <UNFILTERED>
    TEST_LIST = BOOL_OP,OR,COMPOSITE_TEST,<Unused>,TEST_CLAUSE,"TEST @Value(returnert) != 0",Flere
    Flere -> AttributeRemover_3
AttributeRemover_3
    REMOVE_ATTRS = returnert,xml_fragment,xml_id,xml_matched_element,xml_parent_child_pos,xml_parent_id,_url_contents
    -> Loop (output)
Loop (output)

Bookmark: Geometri
Note: Setter geometri ut fra WKT
GeometryReplacer
    KIND_LONG = OGC Well Known Text
    OGC_WKT_PRECISION_DISPLAY = 64-bit
    REMOVE_ATTRIBUTE = Yes
    SOURCE = @Value(geometri)
    -> GeometryExtractor
Note: Eksporterer som GML-geometri
GeometryExtractor
    ATTR = _geometry
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
    -> StringReplacer
Note: Erstater -999999 med NaN
StringReplacer
    CASE = NO
    FIND_TEXT = -999999
    NO_MATCH = _FME_NO_OP_
    REGEXP = NO
    REPLACE_TEXT = NaN
    SRC_ATTRS = _geometry
    -> GeometryReplacer_5
Note: Setter geometri på nytt
GeometryReplacer_5
    KIND_LONG = GML
    REMOVE_ATTRIBUTE = No
    SOURCE = @Value(_geometry)
    SRS_AXIS_ORDER_DISPLAY = Automatic
    -> 3DForcer
Note: Erstatter manglende Z med NaN
3DForcer
    KEEPZVAL = Yes
    ZVALATTR = NaN
    -> GeometryExtractor_2
Note: Tar vare på ny geometri som GML-geometri
GeometryExtractor_2
    ATTR = _geometry
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
    -> BoundingBoxReplacer
Note: Finner utstrekning
BoundingBoxReplacer
    BOXTYPE = 3D Bounding Cube
    BOX -> DimensionExtractor
Note: Finner dimensjon
DimensionExtractor
    DIM_ATTR = _dimension
    -> GeometryReplacer_2
Note: Setter endelig geometri
GeometryReplacer_2
    KIND_LONG = GML
    REMOVE_ATTRIBUTE = No
    SOURCE = @Value(_geometry)
    SRS_AXIS_ORDER_DISPLAY = Automatic
    -> AttributeFilter
AttributeFilter
    ATTR_NAME = _dimension
    ATTR_VALUES = <Empty>,<Missing>,<Null>,<Unfiltered>,2
    <UNFILTERED> -> CoordinateSystemSetter_3
    2 -> 2DForcer
Note: Setter korrekt dimensjon på rene 2D-geometrier
2DForcer
    2D -> CoordinateSystemSetter_3

Bookmark: Splitter multigeometrier
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> NullAttributeMapper
NullAttributeMapper
    ATTRCHOICE = Selected Attributes
    ATTRLIST = _part_number
    NEW_VALUE = 0
    NULL_TREATMENT = New Value
    SOURCE_ATTR_VAL = Null Empty "Missing (Selected Attributes Only)"
    -> StringConcatenator
StringConcatenator
    ACTION = Create New Attribute
    PARM_LINE = @Value(gml_id)_@Value(_part_number)
    VAL_ATTR = gml_id
    -> AttributeRemover_4
