FME workspace NVDBAPI2GML_GenericGML_Step1.fmw

Parameters:
- omr = kommune   # Områdetype
- omrNvn = 403   # Område
- Gdf_fcName = GDF   # GDF Feature Catalogue Name
- gmlFolder = C:\DATA\GitHub\vegvesen\NVDB-Datakatalogen\OWL\FMW   # GML-hovedmappe
- xsdName = network   # skjemanavn
- gmlNs = https://raw.githubusercontent.com/jetgeo/ITSGML/master/XSD   # GML Namespace
- namespace = vegvesen.no.nvdb   # Namespace

Writers:
- GML_2: GML to $(gmlFolder) in EPSG:6173

Creator
    GEOMTYPE = Geometry Object
    NUM = 1
    CREATED -> AttributeManager_4
    CREATED -> AttributeManager_2
AttributeManager_2 [off]
    ATTR_TABLE = SET_TO ftIDs = 5
    -> AttributeSplitter
AttributeManager_4
    ATTR_TABLE = SET_TO ftIDs = 3;5;7;
    -> AttributeSplitter
AttributeSplitter
    ATTR_NAME = ftIDs
    DELIMITER = ;
    DROP_EMPTY_PARTS = No
    LIST_NAME = _ftID
    TRIM_OPTION = Both
    -> ListExploder_2
ListExploder_2
    ATTR_ACCUM_MODE = Merge List Attributes
    ATTR_CONFLICT_RES = Use List Attribute Values
    INDEX_ATTR = _element_index
    LIST_ATTR = _ftID{}
    ELEMENTS -> AttributeCreator_2
AttributeCreator_2
    ATTR_TABLE = SET_TO href = https://www.vegvesen.no/nvdb/api/v2/vegobjekter/@Value(_ftID)?$(omr)=$(omrNvn)&antall=5000&inkluder=alle
    -> NVDB_Leser [_Input]
Note: Leser fagdata
NVDB_Leser
    NESTE.HREF = @Value(href)
    -> PythonCaller
Note: Henter SOSI-navn mm fra NVDB-OWL
PythonCaller
    NEW_ATTRIBUTES = typeName featureTypeReference.xlink_href
    PYTHONSOURCE:
      import fme
      import fmeobjects
      import requests
      import json
      import http.client, urllib.parse
      import xml.etree.ElementTree as ET
      from urllib.parse import unquote
      #https://docs.python.org/3/library/xml.etree.elementtree.html#elementtree-parsing-xml

      def get_nvdb_ft(vot_id):
          #SPARQL-oppslag på en vegobjekttype
          url = "http://rdfspatial.vegdata.no:7200/repositories/nvdb"
          query ="""PREFIX nvdb: <http://rdf.vegdata.no/nvdb/nvdb-owl#>
                      SELECT DISTINCT ?uri ?sosinavn
                      WHERE {
                      ?uri nvdb:nvdb_id """ + vot_id + """ .
                      ?uri nvdb:sosi_navn ?sosinavn .}"""
          r = requests.get(url, params = {"Accept": "application/json", 'query': query})
          return r

      def get_nvdb_pt(vot_id):
          #SPARQL-oppslag på en vegobjekttype sine egenskapstyper
          url = "http://rdfspatial.vegdata.no:7200/repositories/nvdb"
          query = """PREFIX rdfs: <http://www.w3.org/2000/01/rdf-schema#>
                     PREFIX nvdb: <http://rdf.vegdata.no/nvdb/nvdb-owl#>
                     SELECT DISTINCT ?uri ?et_id ?sosinavn ?uom ?codelist_uri
                     WHERE {
                      ?class nvdb:nvdb_id """ + vot_id + """ .
                      ?uri rdfs:domain ?class .
                      ?uri nvdb:nvdb_id ?et_id .
                      ?uri nvdb:sosi_navn ?sosinavn .
                      OPTIONAL {?uri nvdb:enhet ?uom .}
                      OPTIONAL {?uri rdfs:range ?codelist_uri .
          						?codelist_uri nvdb:nvdb_id ?et_id .}
                      }"""
          r = requests.get(url, params = {"Accept": "application/json", 'query': query})
          return r

      def get_nvdb_en(en_id):
          #SPARQL-oppslag på en tillatt verdi (enumeration)
          url = "http://rdfspatial.vegdata.no:7200/repositories/nvdb"
          query = """PREFIX nvdb: <http://rdf.vegdata.no/nvdb/nvdb-owl#>
                     SELECT DISTINCT ?uri ?tv_id ?sosinavn ?nvdbnavn
                     WHERE {
                      ?uri nvdb:nvdb_id  """ + en_id + """ .
                      ?uri nvdb:nvdb_id ?tv_id .
                      ?uri nvdb:nvdb_navn ?nvdbnavn .
                      ?uri nvdb:sosi_navn ?sosinavn .
                      }"""
          r = requests.get(url, params = {"Accept": "application/json", 'query': query})
          return r

      class FeatureProcessor(object):
          def __init__(self):
              pass
          def input(self,feature):
              ftId=feature.getAttribute("fme_feature_type")
              #Kjører spørring for vegobjekttypen mot NVDB-OWL.
              sqres=get_nvdb_ft(ftId)
              #Henter ut sosinavn og uri fra resultatet
              for result in sqres.json()["results"]["bindings"]:
                  sosinavn=result["sosinavn"]["value"]
                  sosinavn.encode(encoding='utf-8',errors='strict')
                  uri=result["uri"]["value"]

              #Endre objekttypenavn
              print("Endrer objekttype " + ftId + " til " + sosinavn + " (" + uri + ")")
              feature.setAttribute("fme_feature_type", sosinavn)
              feature.setAttribute("typeName", sosinavn)
              #Legg til URI
              feature.setAttribute("featureTypeReference.xlink_href", uri)

              #Kjører spørring for vegobjekttypen sine egenskapstyper mot NVDB-OWL
              #! En spørring for hele vegobjekttypen eller en pr egenskapstype?
              sqres=get_nvdb_pt(ftId)

              #Konverter egenskaper til liste "property{}"
              i = 0

              for result in sqres.json()["results"]["bindings"]:
                  et_id = result["et_id"]["value"]
                  sosinavn=result["sosinavn"]["value"]
                  sosinavn.encode(encoding='utf-8',errors='strict')
                  uri=result["uri"]["value"]
                  try:
                      uom=result["uom"]["value"]
                  except:
                      uom=""
                  try:
                      codelist_uri=result["codelist_uri"]["value"]
                      #print("Et_id: " + et_id + " SOSI-navn: " + sosinavn + " uom: " + uom + " datatype-URI: " + codelist_uri)
                  except:
                      codelist_uri=""
                  #print(result)

                  #Løkke for egenskaper. Finner egenskap med angitt id
                  e = feature.getAttribute(et_id)
                  if e != None:
                  #Legger til property med verdier og metadata i listen
                      feature.setAttribute(u'property{%d}.GenericFeatureProperty.memberName' % i, sosinavn)
                      feature.setAttribute(u'property{%d}.GenericFeatureProperty.propertyTypeReference.xlink_href' % i, uri)
                      if uom != "":
                          feature.setAttribute(u'property{%d}.GenericFeatureProperty.unitOfMeasure' % i, uom)
                      #sett propertyStructure og valueReference ut fra codelist_uri
                      if codelist_uri != "":
                          #Kodeliste
                          feature.setAttribute(u'property{%d}.GenericFeatureProperty.propertyStructure' % i, 'listedValue')
                          tvsqres=get_nvdb_en(e)
                          for tvres in tvsqres.json()["results"]["bindings"]:
                              tvuri=tvres["uri"]["value"]
                              tvsosinavn=tvres["sosinavn"]["value"]
                              tvsosinavn.encode(encoding='utf-8',errors='strict')
                              tvnvdbnavn=tvres["nvdbnavn"]["value"]
                              tvnvdbnavn.encode(encoding='utf-8',errors='strict')
                          feature.setAttribute(u'property{%d}.GenericFeatureProperty.valueReference.xlink_href' % i, tvuri)
                          feature.setAttribute(u'property{%d}.GenericFeatureProperty.value' % i, tvnvdbnavn)
                          print(str(sosinavn) + " = " + str(tvnvdbnavn) + " (" + tvuri + ")")
                      else:
                          #Vanlig datatype
                          feature.setAttribute(u'property{%d}.GenericFeatureProperty.propertyStructure' % i, 'simple')
                          feature.setAttribute(u'property{%d}.GenericFeatureProperty.value' % i, e)
                          print(str(sosinavn) + " = " + str(e))


                      i += 1

              self.pyoutput(feature)

          def close(self):
              pass
    PYTHONSYMBOL = FeatureProcessor
    -> AttributeManager_5
    -> NVDB
NVDB: Inspector
    TACKATTRS = fme_feature_type
AttributeManager_5
    ATTR_TABLE:
      RENAME_SET_VALUE startdato > validFrom
      SET_TO beginLifespanVersion = @Value(validFrom)
    -> DateTimeConverter
Feature (writer GML_2)
    attributes: validFrom xml_date, validTo xml_date, beginLifespanVersion xml_datetime, endLifespanVersion xml_datetime, featureTypeReference.nilReason xml_buffer, featureTypeReference.gml_remoteSchema xml_buffer, featureTypeReference.xlink_href xml_buffer, featureTypeReference.xlink_title xml_buffer, featureTypeReference.owns xml_boolean, locationReference{}.AgoraLocationReference.base64String xml_buffer, locationReference{}.AgoraLocationReference.agoraBinaryVersion xml_buffer, locationReference{}.AgoraLocationReference.agoraBinaryVersion.codeSpace xml_buffer, locationReference{}.GeometryLocationReference.encodedGeometry xml_geometry, locationReference{}.LinearLocationReference.name xml_buffer, locationReference{}.LinearLocationReference.description xml_buffer, locationReference{}.LinearLocationReference.networkReference{}.LinkReference.overridingLRM xml_xml, locationReference{}.LinearLocationReference.networkReference{}.LinkReference.element.nilReason xml_buffer, locationReference{}.LinearLocationReference.networkReference{}.LinkReference.element.gml_remoteSchema xml_buffer, locationReference{}.LinearLocationReference.networkReference{}.LinkReference.element.xlink_href xml_buffer, locationReference{}.LinearLocationReference.networkReference{}.LinkReference.element.xlink_title xml_buffer, locationReference{}.LinearLocationReference.networkReference{}.LinkReference.element.owns xml_boolean, locationReference{}.LinearLocationReference.networkReference{}.SimpleLinearReference.overridingLRM xml_xml, locationReference{}.LinearLocationReference.networkReference{}.SimpleLinearReference.element.nilReason xml_buffer, locationReference{}.LinearLocationReference.networkReference{}.SimpleLinearReference.element.gml_remoteSchema xml_buffer, locationReference{}.LinearLocationReference.networkReference{}.SimpleLinearReference.element.xlink_href xml_buffer, locationReference{}.LinearLocationReference.networkReference{}.SimpleLinearReference.element.xlink_title xml_buffer, locationReference{}.LinearLocationReference.networkReference{}.SimpleLinearReference.element.owns xml_boolean, locationReference{}.LinearLocationReference.networkReference{}.SimpleLinearReference.fromPosition.LR_DistanceExpression.distanceAlong xml_real64, locationReference{}.LinearLocationReference.networkReference{}.SimpleLinearReference.fromPosition.LR_DistanceExpression.distanceAlong.uom xml_buffer, locationReference{}.LinearLocationReference.networkReference{}.SimpleLinearReference.toPosition.LR_DistanceExpression.distanceAlong xml_real64,
      locationReference{}.LinearLocationReference.networkReference{}.SimpleLinearReference.toPosition.LR_DistanceExpression.distanceAlong.uom xml_buffer, locationReference{}.LinearLocationReference.networkReference{}.SimplePointReference.overridingLRM xml_xml, locationReference{}.LinearLocationReference.networkReference{}.SimplePointReference.element.nilReason xml_buffer, locationReference{}.LinearLocationReference.networkReference{}.SimplePointReference.element.gml_remoteSchema xml_buffer, locationReference{}.LinearLocationReference.networkReference{}.SimplePointReference.element.xlink_href xml_buffer, locationReference{}.LinearLocationReference.networkReference{}.SimplePointReference.element.xlink_title xml_buffer, locationReference{}.LinearLocationReference.networkReference{}.SimplePointReference.element.owns xml_boolean, locationReference{}.LinearLocationReference.networkReference{}.SimplePointReference.atPosition.LR_DistanceExpression.distanceAlong xml_real64, locationReference{}.LinearLocationReference.networkReference{}.SimplePointReference.atPosition.LR_DistanceExpression.distanceAlong.uom xml_buffer, locationReference{}.LinearLocationReference.networkReference{}.NetworkReference.overridingLRM xml_xml, locationReference{}.LinearLocationReference.networkReference{}.NetworkReference.element.nilReason xml_buffer, locationReference{}.LinearLocationReference.networkReference{}.NetworkReference.element.gml_remoteSchema xml_buffer, locationReference{}.LinearLocationReference.networkReference{}.NetworkReference.element.xlink_href xml_buffer, locationReference{}.LinearLocationReference.networkReference{}.NetworkReference.element.xlink_title xml_buffer, locationReference{}.LinearLocationReference.networkReference{}.NetworkReference.element.owns xml_boolean, locationReference{}.LocationByExternalReference.predefinedLocationReference xml_buffer, locationReference{}.LocationByExternalReference.predefinedLocationReference.codeSpace xml_buffer, locationReference{}.OpenLRLocationReference.binaryLocationReference.BinaryLocationReference.base64String xml_buffer, locationReference{}.OpenLRLocationReference.binaryLocationReference.BinaryLocationReference.openLRBinaryVersion xml_buffer, locationReference{}.OpenLRLocationReference.binaryLocationReference.BinaryLocationReference.openLRBinaryVersion.codeSpace xml_buffer, typeName xml_buffer, typeName.codeSpace xml_buffer, locationReference{}.LinearLocationReference.networkReference{}.LinkReference.applicableDirection xml_buffer, locationReference{}.LinearLocationReference.networkReference{}.SimpleLinearReference.applicableDirection xml_buffer, locationReference{}.LinearLocationReference.networkReference{}.SimplePointReference.applicableDirection xml_buffer, property{}.GenericFeatureProperty.memberName xml_buffer, property{}.GenericFeatureProperty.memberName.codeSpace xml_buffer, property{}.GenericFeatureProperty.propertyStructure xml_buffer, property{}.GenericFeatureProperty.propertyTypeReference.nilReason xml_buffer, property{}.GenericFeatureProperty.propertyTypeReference.gml_remoteSchema xml_buffer,
      property{}.GenericFeatureProperty.propertyTypeReference.xlink_href xml_buffer, property{}.GenericFeatureProperty.propertyTypeReference.xlink_title xml_buffer, property{}.GenericFeatureProperty.propertyTypeReference.owns xml_boolean, property{}.GenericFeatureProperty.value xml_buffer, property{}.GenericFeatureProperty.unitOfMeasure xml_buffer, property{}.GenericFeatureProperty.subproperty{}.GenericFeatureProperty xml_xml, beginLifespanVersion.xsi_nil xml_boolean, validFrom.xsi_nil xml_boolean, property{}.GenericFeatureProperty.valueReference.owns xml_boolean, property{}.GenericFeatureProperty.valueReference.nilReason xml_buffer, property{}.GenericFeatureProperty.valueReference.gml_remoteSchema xml_buffer, property{}.GenericFeatureProperty.valueReference.xlink_href xml_buffer, property{}.GenericFeatureProperty.valueReference.xlink_title xml_buffer

Bookmark: Stedfesting
DateTimeConverter
    DATETIME_ATTR = beginLifespanVersion
    OUT_FORMAT = %Y-%m-%dT%H:%M:%S
    PASSTHROUGH = NO
    REPAIR_INPUT = YES
    -> GeometryExtractor
    <REJECTED> -> GeometryExtractor
GeometryExtractor
    ATTR = GeometryLocationReference.encodedGeometry
    KIND_LONG = GML v3.2.1
    OGCVERSION = 1.2
    OGC_WKT_PRECISION_DISPLAY = 64-bit
    OGEOSMS_URL_PREFIX = http://maps.google.com/?q=
    OMIT_NAMESPACES_DISPLAY = No
    PREFER_POLYGON_OVER_SURFACE = No
    REMOVE_GEOMETRY = No
    -> ListElementCounter
ListElementCounter
    CNT_ATTR = _element_count
    LIST_NAME = LinearLocationReference.networkReference{}
    -> TestFilter
TestFilter
    DEFAULT_VALUE = <UNFILTERED>
    TEST_LIST = "BOOL_OP,OR,COMPOSITE_TEST,""""""<Unused>"""""",TEST_CLAUSE,TEST @Value(_element_count) = 0",noList
    noList -> Aggregator
    <UNFILTERED> -> AttributeRemover_2
    <UNFILTERED> -> AttributeRemover
Note: Fjerne GeometryLocation
AttributeRemover
    REMOVE_ATTRS = GeometryLocationReference.encodedGeometry
    -> Aggregator
Note: Fjerner LinearLocations
AttributeRemover_2
    LIST_ATTRS = LinearLocationReference.networkReference{} LinearLocationReference.networkReference{}.SimpleLinearReference.applicableDirection LinearLocationReference.networkReference{}.SimpleLinearReference.element.xlink_href LinearLocationReference.networkReference{}.SimpleLinearReference.fromPosition.LR_DistanceExpression.distanceAlong LinearLocationReference.networkReference{}.SimpleLinearReference.fromPosition.LR_DistanceExpression.distanceAlong.uom LinearLocationReference.networkReference{}.SimpleLinearReference.toPosition.LR_DistanceExpression.distanceAlong LinearLocationReference.networkReference{}.SimpleLinearReference.toPosition.LR_DistanceExpression.distanceAlong.uom LinearLocationReference.networkReference{}.SimplePointReference.applicableDirection LinearLocationReference.networkReference{}.SimplePointReference.atPosition.LR_DistanceExpression.distanceAlong LinearLocationReference.networkReference{}.SimplePointReference.atPosition.LR_DistanceExpression.distanceAlong.uom LinearLocationReference.networkReference{}.SimplePointReference.element.xlink_href
    -> Aggregator
Note: Slår sammen og bygger liste
Aggregator
    ACCUM_ATTRS_NAME = Use Attributes From One Feature
    AGGREGATE_TYPE = Homogeneous Collection (If Possible)
    GROUP_BY = gml_id
    LIST_ATTRS_TO_INCLUDE = GeometryLocationReference.encodedGeometry LinearLocationReference.networkReference{}.SimpleLinearReference.applicableDirection LinearLocationReference.networkReference{}.SimpleLinearReference.element.xlink_href LinearLocationReference.networkReference{}.SimpleLinearReference.fromPosition.LR_DistanceExpression.distanceAlong LinearLocationReference.networkReference{}.SimpleLinearReference.fromPosition.LR_DistanceExpression.distanceAlong.uom LinearLocationReference.networkReference{}.SimpleLinearReference.toPosition.LR_DistanceExpression.distanceAlong LinearLocationReference.networkReference{}.SimpleLinearReference.toPosition.LR_DistanceExpression.distanceAlong.uom LinearLocationReference.networkReference{}.SimplePointReference.applicableDirection LinearLocationReference.networkReference{}.SimplePointReference.atPosition.LR_DistanceExpression.distanceAlong LinearLocationReference.networkReference{}.SimplePointReference.atPosition.LR_DistanceExpression.distanceAlong.uom LinearLocationReference.networkReference{}.SimplePointReference.element.xlink_href
    LIST_NAME = locationReference
    MODE = Geometry - Assemble One Level
    ORDERED = No
    SEP = ,
    AGGREGATE -> Feature (writer GML_2)

FME custom transformer NVDB_Leser
Leser og tolker data fra NVDB-API

Parameters:
- NESTE.HREF = @Value(neste.href)   # neste.href

_Input (input)
    -> HTTPCaller_2
Loop (input)
    -> HTTPCaller_2
HTTPCaller_2
    CONNECTION_TIMEOUT_LENGTH = 60
    CUSTOM_HEADERS = Accept;application/vnd.vegvesen.nvdb-v2+xml
    ERROR_ATTR = _error
    FOLLOW_REDIRECTS = Yes
    HTTP_METHOD = GET
    RESPONSE_HEADER_LIST_ATTR = _headers
    SAVE_FILE = Attribute
    STATUS_CODE_ATTR = _http_status_code
    TARGET_ATTR = _url_contents
    TARGET_ATTR_ENCODING = auto-detect
    TARGET_URL = @Value(neste.href)
    TRANSFER_TIMEOUT_LENGTH = 90
    USE_COOKIES = No
    VERIFY_SSL_CERTIFICATES = Yes
    -> XMLFragmenter_2
    -> XMLFragmenter
Note: Kan det defineres at et element SKAL blli en liste? Vil i så fall kunne forenkle koden i NVDBTranslator mye. / Se under cardinality under dokumentasjon i XML Fragmenter
Note: Deler opp i en XML pr vegobjekt
XMLFragmenter
    ATTRIBUTE_XML = _url_contents
    EMBEDDED_EXPRESSIONS = vegobjekt
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = id geometri.wkt
    XML_SOURCE_TYPE = Attribute with XML document
    FRAGMENTS -> NVDBTranslator_2
Note: Oversetter fra NVDB-API-XML
NVDBTranslator_2: PythonCaller
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg kommunenummer startdato LinearLocationReference.networkReference{}.SimpleLinearReference.element.xlink_href LinearLocationReference.networkReference{}.SimplePointReference.element.xlink_href LinearLocationReference.networkReference{}.SimpleLinearReference.fromPosition.LR_DistanceExpression.distanceAlong LinearLocationReference.networkReference{}.SimpleLinearReference.toPosition.LR_DistanceExpression.distanceAlong LinearLocationReference.networkReference{}.SimplePointReference.atPosition.LR_DistanceExpression.distanceAlong LinearLocationReference.networkReference{}.SimpleLinearReference.fromPosition.LR_DistanceExpression.distanceAlong.uom LinearLocationReference.networkReference{}.SimpleLinearReference.toPosition.LR_DistanceExpression.distanceAlong.uom LinearLocationReference.networkReference{}.SimplePointReference.atPosition.LR_DistanceExpression.distanceAlong.uom LinearLocationReference.networkReference{}.SimpleLinearReference.applicableDirection LinearLocationReference.networkReference{}.SimplePointReference.applicableDirection
    PYTHONSOURCE:
      import fme
      import fmeobjects

      def extractNVDB_XML(feature):

          ns='vegvesen.no.nvdb' # FME_MacroValues['namespace']

          # Setter feature type
          ft=str(feature.getAttribute('metadata.type.id'))
          feature.setAttribute('fme_feature_type',ft)
          feature.removeAttribute('metadata.type.id')
          # ID og versjon
          feature.setAttribute('identifikasjon.Identifikasjon.navnerom', ns)
          v=feature.getAttribute('id')
          feature.setAttribute('NVDB_ID', v)
          feature.setAttribute('identifikasjon.Identifikasjon.lokalId', v)
          feature.setAttribute('gml_id', ns + '.' + v)
          feature.removeAttribute('id')
          v=feature.getAttribute('metadata.versjon')
          feature.setAttribute('versjonsID', v)
          v=feature.getAttribute('metadata.startdato')
          feature.setAttribute('startdato', v)
          feature.setAttribute('identifikasjon.Identifikasjon.versjonId', v)
          feature.removeAttribute('metadata.versjon')

          # Kommune
          v=feature.getAttribute('lokasjon.kommuner.kommune')
          feature.setAttribute('kommunenummer', v.zfill(4))
          feature.removeAttribute('lokasjon.kommuner.kommune')

          # Henter ut egenskaper
          i = 0
          while True:
              n = feature.getAttribute('egenskaper.egenskap{%d}.id' % i)
              e = str(feature.getAttribute('egenskaper.egenskap{%d}.enum_id' % i))
              v = feature.getAttribute('egenskaper.egenskap{%d}.verdi' % i)
              if v == None:
                  if i>0:
                      break
                  else:
                      # Kun én egenskap, ikke liste
                      n = feature.getAttribute('egenskaper.egenskap.id')
                      e = str(feature.getAttribute('egenskaper.egenskap.enum_id'))
                      v = feature.getAttribute('egenskaper.egenskap.verdi')
                      feature.removeAttribute('egenskaper.egenskap.datatype')
                      feature.removeAttribute('egenskaper.egenskap.datatype_tekst')
                      feature.removeAttribute('egenskaper.egenskap.enhet.id')
                      feature.removeAttribute('egenskaper.egenskap.enhet.kortnavn')
                      feature.removeAttribute('egenskaper.egenskap.enhet.navn')
                      feature.removeAttribute('egenskaper.egenskap.enum_id')
                      feature.removeAttribute('egenskaper.egenskap.id')
                      feature.removeAttribute('egenskaper.egenskap.navn')
                      feature.removeAttribute('egenskaper.egenskap.verdi')

              if n != None:
                  if e == 'None':
                      # if (n == 'Kommunenummer' and v == 0):
                      feature.setAttribute(n, v)
                  else:
                      # Enumverdi for kodelisteverdier
                      feature.setAttribute(n, e)

              feature.removeAttribute('egenskaper.egenskap{%d}.datatype' % i)
              feature.removeAttribute('egenskaper.egenskap{%d}.datatype_tekst' % i)
              feature.removeAttribute('egenskaper.egenskap{%d}.enhet.id' % i)
              feature.removeAttribute('egenskaper.egenskap{%d}.enhet.kortnavn' % i)
              feature.removeAttribute('egenskaper.egenskap{%d}.enhet.navn' % i)
              feature.removeAttribute('egenskaper.egenskap{%d}.enum_id' % i)
              feature.removeAttribute('egenskaper.egenskap{%d}.id' % i)
              feature.removeAttribute('egenskaper.egenskap{%d}.navn' % i)
              feature.removeAttribute('egenskaper.egenskap{%d}.verdi' % i)
              i += 1


          # Geometri
          v=feature.getAttribute('geometri.egengeometri')
          if v != None:
              feature.setAttribute('egengeometri', v)
          if v == 'true':
              feature.setAttribute('prosesshistorie', 'Geometri: Egengeometri fra NVDB')
          else:
              feature.setAttribute('prosesshistorie', 'Geometri: Generert fra lineære referanser til vegnett i NVDB')
          feature.removeAttribute('geometri.egengeometri')
          v=feature.getAttribute('geometri.srid')
          if v != None:
              feature.setAttribute('epsg', 'EPSG:'+v)
          feature.removeAttribute('geometri.srid')
          v=feature.getAttribute('geometri.wkt')
          if v != None:
              feature.setAttribute('geometri', v)
          feature.removeAttribute('geometri.wkt')

          # Stedfesting i basisnettet
          i = 0
          while True:
              v = str(feature.getAttribute('lokasjon.stedfestinger.stedfesting{%d}.veglenkeid' % i))
              if v == 'None':
                  if i>0:
                      break
                  else:
                      # Kun en stedfesting, hent fra attributt i stedet for fra liste
                      v = str(feature.getAttribute('lokasjon.stedfestinger.stedfesting.posisjon'))
                      if v == 'None':
                          #Ikke verdi for "posisjon", dvs strekningsstedfesting (eller ingen!)
                          v = str(feature.getAttribute('lokasjon.stedfestinger.stedfesting.veglenkeid'))
                          if v != 'None':
                              feature.setAttribute(u'LinearLocationReference.networkReference{%d}.SimpleLinearReference.element.xlink_href' % i, 'Network.gml#' + ns + '.rls.' + v)
                              feature.setAttribute(u'LinearLocationReference.networkReference{%d}.SimpleLinearReference.veglenkeid' % i, v)
                              feature.setAttribute(u'LinearLocationReference.networkReference{%d}.SimpleLinearReference.lenkesekvens.Identifikasjon.navnerom' % i, ns + '.rls')
                              feature.setAttribute(u'LinearLocationReference.networkReference{%d}.SimpleLinearReference.lenkesekvens.Identifikasjon.lokalId' % i, v)
                          v = str(feature.getAttribute('lokasjon.stedfestinger.stedfesting.fra_posisjon'))
                          if v != 'None':
                              feature.setAttribute(u'LinearLocationReference.networkReference{%d}.SimpleLinearReference.fromPosition.LR_DistanceExpression.distanceAlong' % i, v)
                              feature.setAttribute(u'LinearLocationReference.networkReference{%d}.SimpleLinearReference.fromPosition.LR_DistanceExpression.distanceAlong.uom' % i, 'interpolative')
                          v = str(feature.getAttribute('lokasjon.stedfestinger.stedfesting.til_posisjon'))
                          if v != 'None':
                              feature.setAttribute(u'LinearLocationReference.networkReference{%d}.SimpleLinearReference.toPosition.LR_DistanceExpression.distanceAlong' % i, v)
                              feature.setAttribute(u'LinearLocationReference.networkReference{%d}.SimpleLinearReference.toPosition.LR_DistanceExpression.distanceAlong.uom' % i, 'interpolative')

                          v = str(feature.getAttribute('lokasjon.stedfestinger.stedfesting.sideposisjon'))
                          if v != 'None':
                              feature.setAttribute(u'LinearLocationReference.networkReference{%d}.SimpleLinearReference.sideposisjon' % i, v)

                          v = str(feature.getAttribute('lokasjon.stedfestinger.stedfesting.retning'))
                          if v != 'None':
                              if v == 'MED':
                                  feature.setAttribute(u'LinearLocationReference.networkReference{%d}.SimpleLinearReference.applicableDirection' % i, 'inDirection')
                              else:
                                  feature.setAttribute(u'LinearLocationReference.networkReference{%d}.SimpleLinearReference.applicableDirection' % i, 'inOppositeDirection')
                          else:
                              feature.setAttribute(u'LinearLocationReference.networkReference{%d}.SimpleLinearReference.applicableDirection' % i, 'bothDirections')

                          feature.setAttribute(u'LinearLocationReference.networkReference{%d}.SimpleLinearReference.lineærReferanseMetode' % i, 'normalisert')

                      else:
                          # Punktstedfesting
                          v = str(feature.getAttribute('lokasjon.stedfestinger.stedfesting.veglenkeid'))
                          if v != 'None':
                              feature.setAttribute(u'LinearLocationReference.networkReference{%d}.SimplePointReference.element.xlink_href' % i, 'Network.gml#' + ns + '.rls.' + v)
                              feature.setAttribute(u'LinearLocationReference.networkReference{%d}.SimplePointReference.veglenkeid' % i, v)
                          feature.setAttribute(u'LinearLocationReference.networkReference{%d}.SimplePointReference.lenkesekvens.Identifikasjon.navnerom'  % i, ns + '.rls')
                          feature.setAttribute(u'LinearLocationReference.networkReference{%d}.SimplePointReference.lenkesekvens.Identifikasjon.lokalId'  % i, v)

                          v = str(feature.getAttribute('lokasjon.stedfestinger.stedfesting.posisjon'))
                          if v != 'None':
                              feature.setAttribute(u'LinearLocationReference.networkReference{%d}.SimplePointReference.atPosition.LR_DistanceExpression.distanceAlong' % i, v)
                              feature.setAttribute(u'LinearLocationReference.networkReference{%d}.SimplePointReference.atPosition.LR_DistanceExpression.distanceAlong.uom' % i, 'interpolative')
                          v = str(feature.getAttribute(u'lokasjon.stedfestinger.stedfesting.sideposisjon'))
                          if v != 'None':
                              feature.setAttribute(u'LinearLocationReference.networkReference{%d}.SimplePointReference.sideposisjon' % i, v)

                          v = str(feature.getAttribute('lokasjon.stedfestinger.stedfesting.sideposisjon'))
                          if v != 'None':
                              feature.setAttribute(u'LinearLocationReference.networkReference{%d}.SimplePointReference.sideposisjon' % i, v)

                          v = str(feature.getAttribute('lokasjon.stedfestinger.stedfesting.retning'))
                          if v != 'None':
                              if v == 'MED':
                                  feature.setAttribute(u'LinearLocationReference.networkReference{%d}.SimplePointReference.applicableDirection' % i, 'inDirection')
                              else:
                                  feature.setAttribute(u'LinearLocationReference.networkReference{%d}.SimplePointReference.applicableDirection' % i, 'inOppositeDirection')
                          else:
                              feature.setAttribute(u'LinearLocationReference.networkReference{%d}.SimplePointReference.applicableDirection' % i, 'bothDirections')



                          feature.setAttribute(u'LinearLocationReference.networkReference{%d}.SimplePointReference.lineærReferanseMetode' % i, 'normalisert')

                      feature.removeAttribute('lokasjon.stedfestinger.stedfesting.veglenkeid')
                      feature.removeAttribute('lokasjon.stedfestinger.stedfesting.fra_posisjon')
                      feature.removeAttribute('lokasjon.stedfestinger.stedfesting.til_posisjon')
                      feature.removeAttribute('lokasjon.stedfestinger.stedfesting.posisjon')
                      feature.removeAttribute('lokasjon.stedfestinger.stedfesting.sideposisjon')
                      # feature.removeAttribute('lokasjon.stedfestinger.stedfesting.retning')
                      feature.removeAttribute('lokasjon.stedfestinger.stedfesting.kortform')
              else:
                  # Bygg LineærPosisjon-liste fra stedfestingsliste
                  v = str(feature.getAttribute('lokasjon.stedfestinger.stedfesting{%d}.posisjon' % i))
                  if v == 'None':
                      #Ikke verdi for "posisjon", dvs strekningsstedfesting
                      v = str(feature.getAttribute('lokasjon.stedfestinger.stedfesting{%d}.veglenkeid' % i))
                      if v != 'None':
                          feature.setAttribute(u'LinearLocationReference.networkReference{%d}.SimpleLinearReference.element.xlink_href' % i, 'Network.gml#' + ns + '.rls.' + v)
                          feature.setAttribute(u'LinearLocationReference.networkReference{%d}.SimpleLinearReference.veglenkeid' % i, v)
                          feature.setAttribute(u'LinearLocationReference.networkReference{%d}.SimpleLinearReference.lenkesekvens.Identifikasjon.navnerom'  % i, ns + '.rls')
                          feature.setAttribute(u'LinearLocationReference.networkReference{%d}.SimpleLinearReference.lenkesekvens.Identifikasjon.lokalId'  % i, v)

                      v = str(feature.getAttribute('lokasjon.stedfestinger.stedfesting{%d}.fra_posisjon' % i))
                      if v != 'None':
                          feature.setAttribute(u'LinearLocationReference.networkReference{%d}.SimpleLinearReference.fromPosition.LR_DistanceExpression.distanceAlong' % i, v)
                          feature.setAttribute(u'LinearLocationReference.networkReference{%d}.SimpleLinearReference.fromPosition.LR_DistanceExpression.distanceAlong.uom' % i, 'interpolative')
                      v = str(feature.getAttribute('lokasjon.stedfestinger.stedfesting{%d}.til_posisjon' % i))
                      if v != 'None':
                          feature.setAttribute(u'LinearLocationReference.networkReference{%d}.SimpleLinearReference.toPosition.LR_DistanceExpression.distanceAlong' % i, v)
                          feature.setAttribute(u'LinearLocationReference.networkReference{%d}.SimpleLinearReference.toPosition.LR_DistanceExpression.distanceAlong.uom' % i, 'interpolative')
                      v = str(feature.getAttribute('lokasjon.stedfestinger.stedfesting{%d}.sideposisjon' % i))
                      if v != 'None':
                          feature.setAttribute(u'LinearLocationReference.networkReference{%d}.SimpleLinearReference.sideposisjon' % i, v)

                      v = str(feature.getAttribute('lokasjon.stedfestinger.stedfesting{%d}.retning' % i))
                      if v != 'None':
                          if v == 'MED':
                              feature.setAttribute(u'LinearLocationReference.networkReference{%d}.SimpleLinearReference.applicableDirection' % i, 'inDirection')
                          else:
                              feature.setAttribute(u'LinearLocationReference.networkReference{%d}.SimpleLinearReference.applicableDirection' % i, 'inOppositeDirection')
                      else:
                          feature.setAttribute(u'LinearLocationReference.networkReference{%d}.SimpleLinearReference.applicableDirection' % i, 'bothDirections')

                      feature.setAttribute(u'LinearLocationReference.networkReference{%d}.SimpleLinearReference.lineærReferanseMetode' % i, 'normalisert')

                  else:
                      # Punktstedfesting
                      v = str(feature.getAttribute('lokasjon.stedfestinger.stedfesting{%d}.veglenkeid' % i))
                      if v != 'None':
                          feature.setAttribute(u'LinearLocationReference.networkReference{%d}.SimplePointReference.element.xlink_href' % i, 'Network.gml#' + ns + '.rls.' + v)
                          feature.setAttribute(u'LinearLocationReference.networkReference{%d}.SimplePointReference.veglenkeid' % i, v)
                          feature.setAttribute(u'LinearLocationReference.networkReference{%d}.SimplePointReference.lenkesekvens.Identifikasjon.navnerom'  % i, ns + '.rls')
                          feature.setAttribute(u'LinearLocationReference.networkReference{%d}.SimplePointReference.lenkesekvens.Identifikasjon.lokalId'  % i, v)

                      v = str(feature.getAttribute('lokasjon.stedfestinger.stedfesting{%d}.posisjon' % i))
                      if v != 'None':
                          feature.setAttribute(u'LinearLocationReference.networkReference{%d}.SimplePointReference.atPosition.LR_DistanceExpression.distanceAlong' % i, v)
                          feature.setAttribute(u'LinearLocationReference.networkReference{%d}.SimplePointReference.atPosition.LR_DistanceExpression.distanceAlong.uom' % i, 'interpolative')
                      v = str(feature.getAttribute('lokasjon.stedfestinger.stedfesting{%d}.sideposisjon' % i))
                      if v != 'None':
                          feature.setAttribute(u'LinearLocationReference.networkReference{%d}.SimplePointReference.sideposisjon' % i, v)

                      v = str(feature.getAttribute('lokasjon.stedfestinger.stedfesting{%d}.retning' % i))
                      if v != 'None':
                          if v == 'MED':
                              feature.setAttribute(u'LinearLocationReference.networkReference{%d}.SimpleLinearReference.applicableDirection' % i, 'inDirection')
                          else:
                              feature.setAttribute(u'LinearLocationReference.networkReference{%d}.SimpleLinearReference.applicableDirection' % i, 'inOppositeDirection')
                      else:
                          feature.setAttribute(u'LinearLocationReference.networkReference{%d}.SimpleLinearReference.applicableDirection' % i, 'bothDirections')

                      feature.setAttribute(u'LinearLocationReference.networkReference{%d}.SimplePointReference.lineærReferanseMetode' % i, 'normalisert')

                  feature.removeAttribute('lokasjon.stedfestinger.stedfesting{%d}.veglenkeid' % i)
                  feature.removeAttribute('lokasjon.stedfestinger.stedfesting{%d}.fra_posisjon' % i)
                  feature.removeAttribute('lokasjon.stedfestinger.stedfesting{%d}.til_posisjon' % i)
                  feature.removeAttribute('lokasjon.stedfestinger.stedfesting{%d}.posisjon' % i)
                  feature.removeAttribute('lokasjon.stedfestinger.stedfesting{%d}.sideposisjon' % i)
                  feature.removeAttribute('lokasjon.stedfestinger.stedfesting{%d}.retning' % i)
                  feature.removeAttribute('lokasjon.stedfestinger.stedfesting{%d}.kortform' % i)
              i += 1

          # Vegreferanse
          i = 0
          while True:
              v = str(feature.getAttribute('lokasjon.vegreferanser.vegreferanse{%d}.kategori' % i))
              if v == 'None':
                  if i>0:
                      break
                  else:
                      # Kun en stedfesting, hent fra attributt i stedet for fra liste
                      v = str(feature.getAttribute('lokasjon.vegreferanser.vegreferanse.kategori'))
                      if v != 'None':
                          feature.setAttribute('vegreferanse{%d}.Vegreferanse.vegkategori' % i, v)
                          feature.removeAttribute('lokasjon.vegreferanser.vegreferanse.kategori')

                      v = str(feature.getAttribute('lokasjon.vegreferanser.vegreferanse.nummer'))
                      if v != 'None':
                          feature.setAttribute('vegreferanse{%d}.Vegreferanse.vegnummer' % i, v)
                          feature.removeAttribute('lokasjon.vegreferanser.vegreferanse.nummer')

                      v = str(feature.getAttribute('lokasjon.vegreferanser.vegreferanse.status'))
                      if v != 'None':
                          feature.setAttribute('vegreferanse{%d}.Vegreferanse.vegstatus' % i, v)
                          feature.removeAttribute('lokasjon.vegreferanser.vegreferanse.status')

                      v = str(feature.getAttribute('lokasjon.vegreferanser.vegreferanse.hp'))
                      if v != 'None':
                          feature.setAttribute('vegreferanse{%d}.Vegreferanse.hovedparsell' % i, v)
                          feature.removeAttribute('lokasjon.vegreferanser.vegreferanse.hp')

                      v = str(feature.getAttribute('lokasjon.vegreferanser.vegreferanse.fra_meter'))
                      if v != 'None':
                          feature.setAttribute('vegreferanse{%d}.Vegreferanse.veglenkeMeterFra' % i, v)
                          feature.removeAttribute('lokasjon.vegreferanser.vegreferanse.fra_meter')

                      v = str(feature.getAttribute('lokasjon.vegreferanser.vegreferanse.til_meter'))
                      if v != 'None':
                          feature.setAttribute('vegreferanse{%d}.Vegreferanse.veglenkeMeterTil' % i, v)
                          feature.removeAttribute('lokasjon.vegreferanser.vegreferanse.til_meter')

                      v = str(feature.getAttribute('lokasjon.vegreferanser.vegreferanse.meter'))
                      if v != 'None':
                          feature.setAttribute('vegreferanse{%d}.Vegreferanse.veglenkeMeterFra' % i, v)
                          feature.setAttribute('vegreferanse{%d}.Vegreferanse.veglenkeMeterTil' % i, v)
                          feature.removeAttribute('lokasjon.vegreferanser.vegreferanse.meter')

                      v = str(feature.getAttribute('lokasjon.vegreferanser.vegreferanse.fylke'))
                      if v != 'None':
                          feature.setAttribute('vegreferanse{%d}.Vegreferanse.fylke' % i, v)
                          feature.removeAttribute('lokasjon.vegreferanser.vegreferanse.fylke')
                      v = str(feature.getAttribute('lokasjon.vegreferanser.vegreferanse.kommune'))
                      if v != 'None':
                          feature.setAttribute('vegreferanse{%d}.Vegreferanse.kommune' % i, v)
                          feature.removeAttribute('lokasjon.vegreferanser.vegreferanse.kommune')

                      feature.removeAttribute('lokasjon.vegreferanser.vegreferanse.kortform')
              else:
                  # Bygg vegreferanse-liste fra stedfestingsliste
                  v = str(feature.getAttribute('lokasjon.vegreferanser.vegreferanse{%d}.fylke'))
                  if v != 'None':
                      feature.setAttribute('vegreferanse{%d}.Vegreferanse.fylke' % i, v)
                      feature.removeAttribute('lokasjon.vegreferanser.vegreferanse{%d}.fylke')
                  else:
                      # Henter fylke fra 'fylker'-taggen
                      v = str(feature.getAttribute('lokasjon.fylker.fylke'))
                      if v != 'None':
                          feature.setAttribute('vegreferanse{%d}.Vegreferanse.fylke' % i, v)
                          feature.removeAttribute('lokasjon.vegreferanser.vegreferanse{%d}.fylke')

                  v = str(feature.getAttribute('lokasjon.vegreferanser.vegreferanse{%d}.kommune'))
                  if v != 'None':
                      feature.setAttribute('vegreferanse{%d}.Vegreferanse.kommune' % i, v)
                      feature.removeAttribute('lokasjon.vegreferanser.vegreferanse{%d}.kommune')
                  else:
                      v = str(feature.getAttribute('lokasjon.vegreferanser.vegreferanse{%d}.kategori' % i))
                      if (v=='K' or v=='P' or v=='S'):
                          # Henter kommune fra 'kommuner'-taggen
                          v = str(feature.getAttribute('lokasjon.kommuner.kommune'))
                          if v != 'None':
                              feature.setAttribute('vegreferanse{%d}.Vegreferanse.kommune' % i, v)
                      else:
                          feature.setAttribute('vegreferanse{%d}.Vegreferanse.kommune' % i, '0')
                      feature.removeAttribute('lokasjon.vegreferanser.vegreferanse{%d}.kommune')

                  v = str(feature.getAttribute('lokasjon.vegreferanser.vegreferanse{%d}.kategori' % i))
                  if v != 'None':
                      feature.setAttribute('vegreferanse{%d}.Vegreferanse.vegkategori' % i, v)
                      feature.removeAttribute('lokasjon.vegreferanser.vegreferanse{%d}.kategori' % i)

                  v = str(feature.getAttribute('lokasjon.vegreferanser.vegreferanse{%d}.nummer' % i))
                  if v != 'None':
                      feature.setAttribute('vegreferanse{%d}.Vegreferanse.vegnummer' % i, v)
                      feature.removeAttribute('lokasjon.vegreferanser.vegreferanse{%d}.nummer' % i)

                  v = str(feature.getAttribute('lokasjon.vegreferanser.vegreferanse{%d}.status' % i))
                  if v != 'None':
                      feature.setAttribute('vegreferanse{%d}.Vegreferanse.vegstatus' % i, v)
                      feature.removeAttribute('lokasjon.vegreferanser.vegreferanse{%d}.status' % i)

                  v = str(feature.getAttribute('lokasjon.vegreferanser.vegreferanse{%d}.hp' % i))
                  if v != 'None':
                      feature.setAttribute('vegreferanse{%d}.Vegreferanse.hovedparsell' % i, v)
                      feature.removeAttribute('lokasjon.vegreferanser.vegreferanse{%d}.hp' % i)

                  v = str(feature.getAttribute('lokasjon.vegreferanser.vegreferanse{%d}.fra_meter' % i))
                  if v != 'None':
                      feature.setAttribute('vegreferanse{%d}.Vegreferanse.veglenkeMeterFra' % i, v)
                      feature.removeAttribute('lokasjon.vegreferanser.vegreferanse{%d}.fra_meter' % i)

                  v = str(feature.getAttribute('lokasjon.vegreferanser.vegreferanse{%d}.til_meter' % i))
                  if v != 'None':
                      feature.setAttribute('vegreferanse{%d}.Vegreferanse.veglenkeMeterTil' % i, v)
                      feature.removeAttribute('lokasjon.vegreferanser.vegreferanse{%d}.til_meter' % i)

                  v = str(feature.getAttribute('lokasjon.vegreferanser.vegreferanse{%d}.meter'))
                  if v != 'None':
                      feature.setAttribute('vegreferanse{%d}.Vegreferanse.veglenkeMeterFra' % i, v)
                      feature.setAttribute('vegreferanse{%d}.Vegreferanse.veglenkeMeterTil' % i, v)
                      feature.removeAttribute('lokasjon.vegreferanser.vegreferanse{%d}.meter')

                  feature.removeAttribute('lokasjon.vegreferanser.vegreferanse{%d}.kortform' % i)
              i += 1


          # Assosiasjoner: Barn
          t = 0
          i = 0
          while True:
              p=str(feature.getAttribute('relasjoner.barn.barn{%d}.type.id' % i))
              lst='false'
              if p == 'None':
                  if i>0:
                      break
                  else:
                      # Kun ett barn, hent assosiert typeid fra attributt i stedet for fra liste
                      typeid = str(feature.getAttribute('relasjoner.barn.barn.type.id'))
                      if typeid != 'None':
                          feature.removeAttribute('relasjoner.barn.barn.type.id')
                          feature.removeAttribute('relasjoner.barn.barn.type.navn')
                      else:
                          # Ingen barn
                          break
              else:
                  #Hent assosiert typeid fra liste
                  lst='true'
                  typeid=str(feature.getAttribute('relasjoner.barn.barn{%d}.type.id' % i))
                  feature.removeAttribute('relasjoner.barn.barn{%d}.type.id' % i)
                  feature.removeAttribute('relasjoner.barn.barn{%d}.type.navn' % i)

              # Løkke for assosierte vegobjekter
              votid='None'
              if lst=='true':
                  #Assosiasjonstyper i liste
                  p = feature.getAttribute('relasjoner.barn.barn{%d}.vegobjekter.id{}' % i)
                  if p == None:
                      # Ikke liste i liste
                      votid=str(feature.getAttribute('relasjoner.barn.barn{%d}.vegobjekter.id' % i))
                      feature.removeAttribute('relasjoner.barn.barn{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'barn')
                      #print votid,t
                      t+=1
                  else:
                      # Løkke for liste med vegobjekt-ider
                      j = 0
                      while True:
                          votid=str(feature.getAttribute('relasjoner.barn.barn{%d}.vegobjekter.id{%d}' % (i,j)))
                          if votid == 'None':
                              break
                          feature.removeAttribute('relasjoner.barn.barn{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              else:
                  # Assosiasjonstype i attributter
                  p = feature.getAttribute('relasjoner.barn.barn.vegobjekter.id{}')
                  if p == None:
                      # Kun ett assosiert objekt
                      votid=str(feature.getAttribute('relasjoner.barn.barn.vegobjekter.id'))
                      feature.removeAttribute('relasjoner.barn.barn.vegobjekter.id')
                      feature.setAttribute('assosiasjoner{%d}.typeId' % t, typeid)
                      feature.setAttribute('assosiasjoner{%d}.vegobjektId' % t, votid)
                      feature.setAttribute('assosiasjoner{%d}.relasjonstype' % t, 'barn')
                      t+=1
                      # print votid,t
                  else:
                      # Løkke for liste med vegobjekt-ider
                      j = 0
                      while True:
                          votid=str(feature.getAttribute('relasjoner.barn.barn.vegobjekter.id{%d}' % j))
                          if votid == 'None':
                              break
                          feature.removeAttribute('relasjoner.barn.barn.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'barn')
                          t+=1
                          j+=1
              i += 1

          # Assosiasjoner: foreldre
          # Må telle videre på samme variabel for ny liste (t), ikke starte på nytt!
          i = 0
          while True:
              p=str(feature.getAttribute('relasjoner.foreldre.forelder{%d}.type.id' % i))
              lst='false'
              if p == 'None':
                  if i>0:
                      break
                  else:
                      # Kun en forelder, hent assosiert typeid fra attributt i stedet for fra liste
                      typeid = str(feature.getAttribute('relasjoner.foreldre.forelder.type.id'))
                      if typeid != 'None':
                          feature.removeAttribute('relasjoner.foreldre.forelder.type.id')
                          feature.removeAttribute('relasjoner.foreldre.forelder.type.navn')
                      else:
                          # Ingen foreldre
                          break
              else:
                  #Hent assosiert typeid fra liste
                  lst='true'
                  typeid=str(feature.getAttribute('relasjoner.foreldre.forelder{%d}.type.id' % i))
                  feature.removeAttribute('relasjoner.foreldre.forelder{%d}.type.id' % i)
                  feature.removeAttribute('relasjoner.foreldre.forelder{%d}.type.navn' % i)

              # Løkke for assosierte vegobjekter
              votid='None'
              if lst=='true':
                  #Assosiasjonstyper i liste
                  p = feature.getAttribute('relasjoner.foreldre.forelder{%d}.vegobjekter.id{}' % i)
                  if p == None:
                      # Ikke liste i liste
                      votid=str(feature.getAttribute('relasjoner.foreldre.forelder{%d}.vegobjekter.id' % i))
                      feature.removeAttribute('relasjoner.foreldre.forelder{%d}.vegobjekter.id' % i)
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder{%d}.vegobjekter.id{%d}' % (i,j)))
                          if votid == 'None':
                              break
                          feature.removeAttribute('relasjoner.foreldre.forelder{%d}.vegobjekter.id{%d}' % (i,j))
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              else:
                  # Assosiasjonstype i attributter
                  p = feature.getAttribute('relasjoner.foreldre.forelder.vegobjekter.id{}')
                  if p == None:
                      # Kun ett assosiert objekt
                      votid=str(feature.getAttribute('relasjoner.foreldre.forelder.vegobjekter.id'))
                      feature.removeAttribute('relasjoner.foreldre.forelder.vegobjekter.id')
                      feature.setAttribute('assosiasjoner{%d}.typeId' % t, typeid)
                      feature.setAttribute('assosiasjoner{%d}.vegobjektId' % t, votid)
                      feature.setAttribute('assosiasjoner{%d}.relasjonstype' % t, 'forelder')
                      t+=1
                  else:
                      # Løkke for liste med vegobjekt-ider
                      j = 0
                      while True:
                          votid=str(feature.getAttribute('relasjoner.foreldre.forelder.vegobjekter.id{%d}' % j))
                          if votid == 'None':
                              break
                          feature.removeAttribute('relasjoner.foreldre.forelder.vegobjekter.id{%d}' % j)
                          feature.setAttribute('assosiasjoner{%d}.typeId' % t, typeid)
                          feature.setAttribute('assosiasjoner{%d}.vegobjektId' % t, votid)
                          feature.setAttribute('assosiasjoner{%d}.relasjonstype' % t, 'forelder')
                          t+=1
                          j+=1
              i += 1
    PYTHONSYMBOL = extractNVDB_XML
    -> GeometryReplacer
Note: Geometri
GeometryReplacer
    KIND_LONG = OGC Well Known Text
    OGC_WKT_PRECISION_DISPLAY = 64-bit
    REMOVE_ATTRIBUTE = Yes
    SOURCE = @Value(geometri)
    -> CoordinateSystemSetter
    -> CoordinateSystemSetter_2
    -> 3DForcer
3DForcer
    KEEPZVAL = Yes
    ZVALATTR = NaN
    -> CoordinateSystemSetter_3
CoordinateSystemSetter_3
    COORDSYS = EPSG:6173
    -> Deaggregator
CoordinateSystemSetter [off]
    COORDSYS = @Value(epsg)
    -> Deaggregator
CoordinateSystemSetter_2 [off]
    COORDSYS = EPSG:25833
    -> Deaggregator
XMLFragmenter_2
    ATTRIBUTE_XML = _url_contents
    EMBEDDED_EXPRESSIONS = side/metadata
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = returnert neste.href
    XML_SOURCE_TYPE = Attribute with XML document
    FRAGMENTS -> TestFilter
TestFilter
    DEFAULT_VALUE = <UNFILTERED>
    TEST_LIST = BOOL_OP,OR,COMPOSITE_TEST,<Unused>,TEST_CLAUSE,"TEST @Value(returnert) != 0",Flere
    Flere -> Loop (output)
Loop (output)

Bookmark: Splitter multigeometrier
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> NullAttributeMapper
NullAttributeMapper
    ATTRCHOICE = Selected Attributes
    ATTRLIST = _part_number
    NEW_VALUE = 0
    NULL_TREATMENT = New Value
    SOURCE_ATTR_VAL = Null Empty "Missing (Selected Attributes Only)"
    -> StringConcatenator
StringConcatenator
    ACTION = Create New Attribute
    PARM_LINE = @Value(gml_id)_@Value(_part_number)
    VAL_ATTR = gml_id
    -> Output (output)
Output (output)
